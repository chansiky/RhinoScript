Option Explicit
'Script written by <insert name>
'Script copyrighted by <insert company name>
'Script version Monday, 03 June 2013 11:48:57

Call Main()
Sub Main()

	Dim strCrvs,origCrv, dirPt,OffsetAmount, OffsetCurve
	Dim Mullion_Face, Mullion_Depth, Mullion_Height,Slab_Height
	Dim Crv_Mull_Outside, Crv_Mull_Inside
	Dim Srf_Mull_Profile,Srf_Slab_Profile
	Dim PSrf_Mull,PSrf_Mull2,PSrf_Slab
	Dim Crv_Dir_MullHeight, Crv_Dir_SlabHeight
	Dim Crv_MullJt_A,Crv_MullJt_B
	
	Mullion_Face = 50
	Mullion_Depth = 150
	Mullion_Height = 75
	Slab_Height = 1300
	
	Crv_Dir_MullHeight = Rhino.AddCurve(Array(Array(0, 0, 0), Array(0, 0, -Mullion_Height)))
	Crv_Dir_SlabHeight = Rhino.AddCurve(Array(Array(0, 0, 0), Array(0, 0, -Slab_Height)))
	
	AddNewLayer("Slab")
	AddNewLayer("Slab::Mullions-H")
	AddNewLayer("Slab::Slab")
	AddNewLayer("Slab::Joints-H")
	
	strCrvs = Rhino.GetObjects("select Curves to Offset", 4,, 1)
	If Not IsNull(strCrvs) Then
		dirPt = Rhino.GetPoint("select point to Offset All curves")
		If Not IsNull(dirPt) Then
			For Each origCrv In strCrvs
				If Not IsNull(origCrv) Then
					Crv_Mull_Outside = Rhino.OffsetCurve(origCrv, dirPt, Mullion_Face)
					Crv_Mull_Inside = Rhino.OffsetCurve(origCrv, dirPt, Mullion_Face + Mullion_Depth)
					If Rhino.IsCurveClosed(Crv_Mull_Outside(0)) And Rhino.IsCurveClosed(Crv_Mull_Inside(0)) Then
						Srf_Mull_Profile = Rhino.AddPlanarSrf(Array(Crv_Mull_Outside(0), Crv_Mull_Inside(0)))
						PSrf_Mull = Rhino.ExtrudeSurface(Srf_Mull_Profile(0), Crv_Dir_MullHeight, True)
						Rhino.ObjectColor PSrf_Mull, RGB(90, 70, 170)
						PSrf_Mull2 = Rhino.CopyObject(PSrf_Mull, Array(0, 0, 0), Array(0, 0, Mullion_Height - Slab_Height))
						rhino.ObjectLayer PSrf_Mull, "Slab::Mullions-H"
						rhino.ObjectLayer PSrf_Mull2, "Slab::Mullions-H"
					End If
					Crv_MullJt_A = Rhino.CopyObject(origCrv, Array(0, 0, 0), Array(0, 0, -(Mullion_Height / 2)))
					Rhino.ObjectColor Crv_MullJt_A, RGB(220, 0, 125)
					Crv_MullJt_B = Rhino.CopyObject(origCrv, Array(0, 0, 0), Array(0, 0, -(Slab_Height - (Mullion_Height / 2))))
					Rhino.ObjectColor Crv_MullJt_B, RGB(220, 0, 125)
					
					rhino.ObjectLayer Crv_MullJt_A, "Slab::Joints-H"
					rhino.ObjectLayer Crv_MullJt_B, "Slab::Joints-H"
					
					If Rhino.IsCurveClosed(Crv_Mull_Inside(0)) Then
						rhino.Print "yes"
						Srf_Slab_Profile = Rhino.AddPlanarSrf(Crv_Mull_Inside(0))
						PSrf_Slab = Rhino.ExtrudeSurface(Srf_Slab_Profile(0), Crv_Dir_SlabHeight, True)
						Rhino.ObjectColor PSrf_Slab, RGB(180, 180, 150)
						rhino.ObjectLayer PSrf_Slab, "Slab::Slab"
					End If
				End If
				
				Rhino.DeleteObject(Crv_Mull_Outside(0))
				Rhino.DeleteObject(Crv_Mull_Inside(0))
				Rhino.DeleteObject(Srf_Mull_Profile(0))
				Rhino.DeleteObject(Srf_Slab_Profile(0))
				
				
			Next
	
		End If
	End If
	
	Rhino.DeleteObject(Crv_Dir_SlabHeight)
	Rhino.DeleteObject(Crv_Dir_MullHeight)
	
	
End Sub

Function AddNewLayer(ByVal lay_name)
	
	If Not rhino.IsLayer(lay_name) Then
		rhino.AddLayer(lay_name)
	End If
	
End Function
