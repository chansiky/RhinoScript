Option Explicit
'Script written by <insert name>
'Script copyrighted by <insert company name>
'Script version Tuesday, March 18, 2014 9:55:35 AM


Call Main()
Sub Main()
	
	
	Dim strObj

	int_level = Empty
	
	arrObjs = Empty
	

End Sub
