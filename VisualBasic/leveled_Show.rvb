Option Explicit
'Script written by <insert name>
'Script copyrighted by <insert company name>
'Script version Tuesday, March 18, 2014 2:08:49 PM
Private int_level


If IsEmpty(arrObjs) Then
	rhino.Print "arrObjs was not an object; arrObjs created."
	Private arrObjs()
End If
'
If IsEmpty(int_level) Then
	rhino.Print "int_level was empty; int_level set to 0."
	int_level = 0
	ReDim Preserve arrObjs(int_level)
End If



'Private int_level
'Private arrObjs()
Call Main()
Sub Main()
	
	If int_level < 0 Then
		
		rhino.Print "no more levels to show - showing all"
		rhino.Command "show"
		Exit Sub
	End If
	If Not IsArray(arrObjs) Then
		
		rhino.Print "arrObjs not array"
		
		Exit Sub
	End If

	
	If Not IsArray(arrObjs(int_level)) Then
		
		rhino.Print "arrObjs(int_level) not array"
		rhino.Command "show"
		Exit Sub
	End If
	

	rhino.Print int_level
	rhino.print "Ubound(arrObjs) = " & Ubound(arrObjs)
	
	
	LevelShowLoop()
	
		
	''	
	rhino.print "variable type of arrObjs(" & int_level & ")" & VarType(arrObjs(int_level))
	''	
	
	rhino.ShowObjects(arrObjs(int_level))
	rhino.Print "level " & int_level & " shown"
	int_level = int_level - 1
End Sub

Function LevelShowLoop()
	
	If int_level + 1 <= Ubound(arrObjs) Then
		If Not LevelShownCheck(int_level + 1) Then
			rhino.Print "a"
			int_level = int_level + 1
			LevelShowLoop()
		End If
	End If
	If int_level >= Ubound(arrObjs) Then
		
		rhino.Print "b"
		int_level = Ubound(arrObjs)
	End If
	
End Function

Function LevelHiddenCheck(ByVal i)

	Dim strObject
	Dim levelHidden
	levelHidden = True
	
	If Not IsNull(arrObjs(i)) Then
		
		rhino.Print "level " & i & " is Empty???"
		LevelHiddenCheck = False
		Exit Function
		
	End If
	
	If Not IsArray(arrObjs(i)) Then
		
		rhino.Print "level " & i & " is not an array???"
		LevelHiddenCheck = False
		Exit Function
		
	End If
	For Each strObject In arrObjs(i)
		If Not Rhino.IsObjectHidden(strObject) Then
			
			rhino.Print "level " & i & " is not hidden"
			levelHidden = False
			LevelHiddenCheck = False
			Exit For
		End If

	Next
	
	
	'''
	If LevelHidden Then
		rhino.Print "level " & i & " is hidden"
		LevelHiddenCheck = True
	End If
	'''

End Function


Function LevelShownCheck(ByVal i)
	
	
	Dim strObject
	Dim levelShown
	levelShown = False
	
	If IsNull(arrObjs(i)) Then
		
		rhino.Print "level " & i & " is Null???"
		LevelShownCheck = False
		Exit Function
		
	End If
	
	If Not IsArray(arrObjs(i)) Then
		
		rhino.Print "level " & i & " is not an array???"
		LevelShownCheck = False
		Exit Function
		
	End If
	
	For Each strObject In arrObjs(i)
		If Not Rhino.IsObjectHidden(strObject) Then
			
			rhino.Print "level " & i & " is shown"
			levelShown = True
			LevelShownCheck = True
			Exit For
		End If

	Next
	
		
	'''
	If Not LevelShown Then
		rhino.Print "level " & i & " is shown"
		LevelShownCheck = False
	End If
	'''
	
	
End Function
