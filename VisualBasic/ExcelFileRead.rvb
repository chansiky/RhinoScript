' Description:
 '   Reads a Microsoft Excel file.
 ' Parameters:
 '   strFile - [in] The name of the Excel file to read.
 ' Returns:
 '   A two-dimension array of cell values, if successful.
 '   Null on error
Option Explicit

Dim RowCount
Dim ColCount


Call Main()


Sub Main()
	Dim mx_data
	Dim str_data
 
	mx_data = ReadExcelFile("C:\cy\Render_cameras.xlsx")
	
	rhino.Print mx_data(0, 1)
	

End Sub


Function ReadExcelFile(ByVal strFile)
 
	' Local variable declarations
	Dim objExcel, objSheet, objCells
	Dim nUsedRows, nUsedCols, nTop, nLeft, nRow, nCol
	Dim arrSheet()
 
	' Default return value 
	ReadExcelFile = Null
 
	' Create the Excel object
	On Error Resume Next
	Set objExcel = CreateObject("Excel.Application")
	If (Err.Number <> 0) Then
		Exit Function
	End If
 
	' Don't display any alert messages
	objExcel.DisplayAlerts = 0  
 
	' Open the document as read-only
	On Error Resume Next
	Call objExcel.Workbooks.Open(strFile, False, True)
	If (Err.Number <> 0) Then
		Exit Function
	End If
 
	' If you wanted to read all sheets, you could call
	' objExcel.Worksheets.Count to get the number of sheets
	' and the loop through each one. But in this example, we
	' will just read the first sheet.
	Set objSheet = objExcel.ActiveWorkbook.Worksheets(1)
 
	' Get the number of used rows
	nUsedRows = objSheet.UsedRange.Rows.Count
 
	' Get the number of used columns
	nUsedCols = objSheet.UsedRange.Columns.Count
 
	' Get the topmost row that has data
	nTop = objSheet.UsedRange.Row
 
	' Get leftmost column that has data
	nLeft = objSheet.UsedRange.Column

	' Get the used cells
	Set objCells = objSheet.Cells
 
	' Dimension the sheet array
	ReDim arrSheet(nUsedRows - 1, nUsedCols - 1)
	RowCount = nUsedRows - 1
	ColCount = nUsedCols - 1
	' Loop through each row 
	For nRow = 0 To (nUsedRows - 1)
		' Loop through each column 
		For nCol = 0 To (nUsedCols - 1)
			' Add the cell value to the sheet array 
			arrSheet(nRow, nCol) = objCells(nRow + nTop, nCol + nLeft).Value
		Next
	Next
 
	' Close the workbook without saving
	Call objExcel.ActiveWorkbook.Close(False)
 
	' Quit Excel
	objExcel.Application.Quit
 
	' Return the sheet data to the caller
	ReadExcelFile = arrSheet
 
End Function
