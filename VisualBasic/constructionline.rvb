Option Explicit
'Script written by <insert name>
'Script copyrighted by <insert company name>
'Script version Sunday, April 11, 2010 9:17:05 PM

Call Main()
Sub Main()

	Dim preselection
	Dim point0,point1,point2
	Dim vector1, vector2, vector3
	Dim line1,line2
	Dim selection
	
	Dim lay_name
	lay_name = "Temporary::construction"
	
	preselection = rhino.selectedobjects
	If isarray(preselection) Then
		preselection = rhino.getobjects("", 0, True, True)
	End If




	
	rhino.Command "_line"

	line1 = Rhino.LastCreatedObjects 
	If isnull(line1) Then
		Exit Sub
	End If
	point0 = rhino.curvepoints(line1(0))
	
	vector1 = rhino.vectorcreate(point0(0), point0(1))
	vector2 = rhino.VectorScale(vector1, 100)
	vector3 = rhino.VectorReverse(vector2)
	
	point1 = rhino.pointadd(point0(0), vector2)
	point2 = rhino.PointAdd(point0(1), vector3)
	line2 = rhino.AddLine(point1, point2)
	
	rhino.DeleteObject(line1(0))
	

	
	Dim strobject, strobjectnew
	Dim strlayer
	
	If Not rhino.IsLayer(lay_name) Then
		strlayer = rhino.AddLayer(lay_name, RGB(148, 189, 225))
	End If
	
	If rhino.IsLayer(lay_name) Then
		strobject = line2
		strobjectnew = rhino.ObjectLayer(strobject, lay_name)
		rhino.unselectallobjects
	End If
	If isarray(preselection) Then 
		rhino.selectobjects(preselection)
	End If
End Sub
