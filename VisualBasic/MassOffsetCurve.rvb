Option Explicit
'Script written by <insert name>
'Script copyrighted by <insert company name>
'Script version Monday, 03 June 2013 11:48:57

Call Main()
Sub Main()

	Dim strCrvs,origCrv, dirPt,OffsetAmount, OffsetCurve
	
	strCrvs = Rhino.GetObjects("select Curves to Offset", 4,, 1)
	If Not IsNull(strCrvs) Then
		dirPt = Rhino.GetPoint("select point to Offset All curves")
		If Not IsNull(dirPt) Then
			OffsetAmount = Rhino.GetReal("Enter Offset Amount")
			If Not IsNull(OffsetAmount) Then
				
				For Each origCrv In strCrvs
		
		
					If Not IsNull(origCrv) Then
		
						OffsetCurve = Rhino.OffsetCurve(origCrv, dirPt, OffsetAmount)
			
					End If
		
			
			
			
				Next
	
			End If
		End If
	End If



	
	
End Sub
